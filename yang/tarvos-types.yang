module tarvos-types {
  yang-version 1.1;
  namespace "urn:tarvos:params:xml:ns:yang:tarvos-types";
  prefix ttypes;

  organization
    "Tarvos Network OS";
  contact
    "Tarvos project";
  description
    "Common types for the Tarvos routing modules (tarvos-bgp, tarvos-ospf,
     tarvos-isis, tarvos-frr, tarvos-vxlan).

     Copyright 2026 Tarvos contributors. Licensed under the Apache License 2.0.";

  revision 2026-11-13 {
    description
      "Initial revision.";
  }

  typedef interface-name {
    type string {
      length "1..15";
      pattern '[A-Za-z0-9_.:@-]+';
    }
    description
      "Linux network interface name.";
  }

  typedef vrf-name {
    type string {
      length "1..15";
      pattern '[A-Za-z0-9_.-]+';
    }
    description
      "VRF name. 'default' is the main routing table.";
  }

  typedef object-name {
    type string {
      length "1..63";
      pattern '[A-Za-z0-9_.-]+';
    }
    description
      "Name of an FRR object (route-map, prefix-list, peer-group, profile, ...).";
  }

  typedef as-number {
    type uint32 {
      range "1..4294967295";
    }
    description
      "Autonomous system number (4-byte, asplain).";
  }

  typedef route-distinguisher {
    type string {
      pattern '([0-9]{1,10}|[0-9]{1,3}(\.[0-9]{1,3}){3}):[0-9]{1,10}';
    }
    description
      "Route distinguisher, ASN:NN or IPv4:NN (for example 65000:100 or
      10.0.0.1:100).";
  }

  typedef route-target {
    type string {
      pattern '([0-9]{1,10}|[0-9]{1,3}(\.[0-9]{1,3}){3}|\*):[0-9]{1,10}';
    }
    description
      "Route target, ASN:NN or IPv4:NN. '*:NN' matches any AS (import only).";
  }

  typedef vni {
    type uint32 {
      range "1..16777215";
    }
    description
      "VXLAN network identifier.";
  }

  typedef ip-address-with-prefix-length {
    type union {
      type string {
        pattern '(([0-9]|[1-9][0-9]|1[0-9]{2}|2[0-4][0-9]|25[0-5])\.){3}'
              + '([0-9]|[1-9][0-9]|1[0-9]{2}|2[0-4][0-9]|25[0-5])'
              + '/([0-9]|[1-2][0-9]|3[0-2])';
      }
      type string {
        pattern '[0-9a-fA-F:]*:[0-9a-fA-F:.]*/([0-9]|[1-9][0-9]|1[01][0-9]|12[0-8])';
      }
    }
    description
      "Interface address with its prefix length, for example 10.1.100.1/24 (unlike
       inet:ip-prefix, the host bits are kept).";
  }

  typedef description-string {
    type string {
      length "1..80";
      pattern '[A-Za-z0-9 _.,:/()+=@#-]+';
    }
    description
      "Free-form description (single line, no special CLI characters).";
  }
}
